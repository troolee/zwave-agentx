ZEYE-MIB DEFINITIONS ::= BEGIN

--
-- Zeye MIB objects (.1.3.6.1.4.1.47015)
--

IMPORTS
    MODULE-IDENTITY, enterprises, OBJECT-TYPE, Integer32
        FROM SNMPv2-SMI
    TEXTUAL-CONVENTION, DisplayString
        FROM SNMPv2-TC
    MODULE-COMPLIANCE, OBJECT-GROUP
        FROM SNMPv2-CONF
;

zeye MODULE-IDENTITY
    LAST-UPDATED    "201604220000Z"
    ORGANIZATION    "Zeye Solutions"
    CONTACT-INFO    "info@zeye.ws"
    DESCRIPTION     "Zeye SNMP Definition"

    REVISION        "201604220000Z"
    DESCRIPTION     "Zeye 0.2.0.0 MIB"

    ::= { enterprises 47015 }


Boolean ::= TEXTUAL-CONVENTION
    STATUS              current
    DESCRIPTION
        "Represents a boolean value."
    SYNTAX              INTEGER { true(1), false(2) }


Numeric2 ::= TEXTUAL-CONVENTION
    DISPLAY-HINT        "d-2"
    STATUS              current
    DESCRIPTION
        "Represents a numeric with 2 decimals value."
    SYNTAX              INTEGER(-2147483648..2147483648)


zeyeInfo                OBJECT IDENTIFIER ::= { zeye 2 }

zeyeAgentVersion OBJECT-TYPE
    SYNTAX              DisplayString
    MAX-ACCESS          read-write
    STATUS              current
    DESCRIPTION
        "Zeye SNMP Agent version"
    ::= { zeyeInfo 1 }

zwave                   OBJECT IDENTIFIER ::= { zeye 3 }
zwaveNodes              OBJECT IDENTIFIER ::= { zwave 1 }
zwaveSensors            OBJECT IDENTIFIER ::= { zwave 2 }
zwaveTemperatureSensors OBJECT IDENTIFIER ::= { zwaveSensors 1 }
zwaveUltravioletSensors OBJECT IDENTIFIER ::= { zwaveSensors 2 }
zwaveLuminanceSensors   OBJECT IDENTIFIER ::= { zwaveSensors 3 }
zwaveHumiditySensors    OBJECT IDENTIFIER ::= { zwaveSensors 4 }

zwaveNodesCount OBJECT-TYPE
    SYNTAX              Integer32
    MAX-ACCESS          read-write
    STATUS              current
    DESCRIPTION
        "Z-wave nodes count"
    ::= { zwaveNodes 1 }

zwaveNodesTable OBJECT-TYPE
    SYNTAX              SEQUENCE OF ZwaveNodesEntry
    MAX-ACCESS          not-accessible
    STATUS              current
    DESCRIPTION
        "Z-wave nodes table"
    ::= { zwaveNodes 2 }

zwaveNodesEntry OBJECT-TYPE
    SYNTAX              ZwaveNodesEntry
    MAX-ACCESS          not-accessible
    STATUS              current
    DESCRIPTION
	   "Z-wave node entry"
    INDEX   { zwaveNodeIndex }
    ::= { zwaveNodesTable 1 }

ZwaveNodesEntry ::= SEQUENCE {
    zwaveNodeIndex      INTEGER(0..255),
    zwaveNodeId         Integer32,
    zwaveNodeName       DisplayString,
    zwaveNodeLocation   DisplayString,
    zwaveNodeBaud       Integer32,
    zwaveNodeBattery    Integer32,
    zwaveNodeAwaked     Boolean,
    zwaveNodeType       DisplayString,
    zwaveNodeTypeName   DisplayString
}

zwaveNodeIndex OBJECT-TYPE
    SYNTAX              INTEGER(0..255)
    MAX-ACCESS          not-accessible
    STATUS              current
    DESCRIPTION
        "Z-wave node index"
    ::= { zwaveNodesEntry 1 }

zwaveNodeId OBJECT-TYPE
    SYNTAX              Integer32
    MAX-ACCESS          read-write
    STATUS              current
    DESCRIPTION
        "Z-wave node Id"
    ::= { zwaveNodesEntry 2 }

zwaveNodeName OBJECT-TYPE
    SYNTAX              DisplayString
    MAX-ACCESS          read-write
    STATUS              current
    DESCRIPTION
        "Z-wave node name"
    ::= { zwaveNodesEntry 3 }

zwaveNodeLocation OBJECT-TYPE
    SYNTAX              DisplayString
    MAX-ACCESS          read-write
    STATUS              current
    DESCRIPTION
        "Z-wave node location"
    ::= { zwaveNodesEntry 4 }

zwaveNodeBaud OBJECT-TYPE
    SYNTAX              Integer32
    MAX-ACCESS          read-write
    STATUS              current
    DESCRIPTION
        "Z-wave node baud"
    ::= { zwaveNodesEntry 5 }

zwaveNodeBattery OBJECT-TYPE
    SYNTAX              Integer32
    MAX-ACCESS          read-write
    STATUS              current
    DESCRIPTION
        "Z-wave node battery level"
    ::= { zwaveNodesEntry 6 }

zwaveNodeAwaked OBJECT-TYPE
    SYNTAX              Boolean
    MAX-ACCESS          read-write
    STATUS              current
    DESCRIPTION
        "Z-wave node awaked status"
    ::= { zwaveNodesEntry 7 }

zwaveNodeType OBJECT-TYPE
    SYNTAX              DisplayString
    MAX-ACCESS          read-write
    STATUS              current
    DESCRIPTION
        "Z-wave node type"
    ::= { zwaveNodesEntry 8 }

zwaveNodeTypeName OBJECT-TYPE
    SYNTAX              DisplayString
    MAX-ACCESS          read-write
    STATUS              current
    DESCRIPTION
        "Z-wave node type name"
    ::= { zwaveNodesEntry 9 }

--- Temperature Sensors

zwaveTemperatureSensorsCount OBJECT-TYPE
    SYNTAX              Integer32
    MAX-ACCESS          read-write
    STATUS              current
    DESCRIPTION
        "Z-wave temperature sensors count"
    ::= { zwaveTemperatureSensors 1 }

zwaveTemperatureSensorsTable OBJECT-TYPE
    SYNTAX              SEQUENCE OF ZwaveTemperatureSensorsEntry
    MAX-ACCESS          not-accessible
    STATUS              current
    DESCRIPTION
        "Z-wave temperature sensors table"
    ::= { zwaveTemperatureSensors 2 }

zwaveTemperatureSensorsEntry OBJECT-TYPE
    SYNTAX              ZwaveTemperatureSensorsEntry
    MAX-ACCESS          not-accessible
    STATUS              current
    DESCRIPTION
	   "Z-wave temperature sensots entry"
    INDEX   { zwaveTemperatureSensorIndex }
    ::= { zwaveTemperatureSensorsTable 1 }

ZwaveTemperatureSensorsEntry ::= SEQUENCE {
    zwaveTemperatureSensorIndex     INTEGER(0..255),
    zwaveTemperatureSensorNodeId    Integer32,
    zwaveTemperatureSensorId        DisplayString,
    zwaveTemperatureSensorName      DisplayString,
    zwaveTemperatureSensorLocation  DisplayString,
    zwaveTemperatureSensorValue     Numeric2
}

zwaveTemperatureSensorIndex OBJECT-TYPE
    SYNTAX              INTEGER(0..255)
    MAX-ACCESS          not-accessible
    STATUS              current
    DESCRIPTION
        "Z-wave temperature sensor index"
    ::= { zwaveTemperatureSensorsEntry 1 }

zwaveTemperatureSensorNodeId OBJECT-TYPE
    SYNTAX              Integer32
    MAX-ACCESS          read-write
    STATUS              current
    DESCRIPTION
        "Z-wave temperature sensor node id"
    ::= { zwaveTemperatureSensorsEntry 2 }

zwaveTemperatureSensorId OBJECT-TYPE
    SYNTAX              DisplayString
    MAX-ACCESS          read-write
    STATUS              current
    DESCRIPTION
        "Z-wave temperature sensor id"
    ::= { zwaveTemperatureSensorsEntry 3 }

zwaveTemperatureSensorName OBJECT-TYPE
    SYNTAX              DisplayString
    MAX-ACCESS          read-write
    STATUS              current
    DESCRIPTION
        "Z-wave temperature sensor name"
    ::= { zwaveTemperatureSensorsEntry 4 }

zwaveTemperatureSensorLocation OBJECT-TYPE
    SYNTAX              DisplayString
    MAX-ACCESS          read-write
    STATUS              current
    DESCRIPTION
        "Z-wave temperature sensor location"
    ::= { zwaveTemperatureSensorsEntry 5 }

zwaveTemperatureSensorValue OBJECT-TYPE
    SYNTAX              Numeric2
    MAX-ACCESS          read-write
    STATUS              current
    DESCRIPTION
        "Z-wave temperature sensor value (C)"
    ::= { zwaveTemperatureSensorsEntry 6 }

--- Ultraviolet Sensors

zwaveUltravioletSensorsCount OBJECT-TYPE
    SYNTAX              Integer32
    MAX-ACCESS          read-write
    STATUS              current
    DESCRIPTION
        "Z-wave ultraviolet sensors count"
    ::= { zwaveUltravioletSensors 1 }

zwaveUltravioletSensorsTable OBJECT-TYPE
    SYNTAX              SEQUENCE OF ZwaveUltravioletSensorsEntry
    MAX-ACCESS          not-accessible
    STATUS              current
    DESCRIPTION
        "Z-wave ultraviolet sensors table"
    ::= { zwaveUltravioletSensors 2 }

zwaveUltravioletSensorsEntry OBJECT-TYPE
    SYNTAX              ZwaveUltravioletSensorsEntry
    MAX-ACCESS          not-accessible
    STATUS              current
    DESCRIPTION
	   "Z-wave ultraviolet sensots entry"
    INDEX   { zwaveUltravioletSensorIndex }
    ::= { zwaveUltravioletSensorsTable 1 }

ZwaveUltravioletSensorsEntry ::= SEQUENCE {
    zwaveUltravioletSensorIndex     INTEGER(0..255),
    zwaveUltravioletSensorNodeId    Integer32,
    zwaveUltravioletSensorId        DisplayString,
    zwaveUltravioletSensorName      DisplayString,
    zwaveUltravioletSensorLocation  DisplayString,
    zwaveUltravioletSensorValue     Numeric2
}

zwaveUltravioletSensorIndex OBJECT-TYPE
    SYNTAX              INTEGER(0..255)
    MAX-ACCESS          not-accessible
    STATUS              current
    DESCRIPTION
        "Z-wave ultraviolet sensor index"
    ::= { zwaveUltravioletSensorsEntry 1 }

zwaveUltravioletSensorNodeId OBJECT-TYPE
    SYNTAX              Integer32
    MAX-ACCESS          read-write
    STATUS              current
    DESCRIPTION
        "Z-wave ultraviolet sensor node id"
    ::= { zwaveUltravioletSensorsEntry 2 }

zwaveUltravioletSensorId OBJECT-TYPE
    SYNTAX              DisplayString
    MAX-ACCESS          read-write
    STATUS              current
    DESCRIPTION
        "Z-wave ultraviolet sensor id"
    ::= { zwaveUltravioletSensorsEntry 3 }

zwaveUltravioletSensorName OBJECT-TYPE
    SYNTAX              DisplayString
    MAX-ACCESS          read-write
    STATUS              current
    DESCRIPTION
        "Z-wave ultraviolet sensor name"
    ::= { zwaveUltravioletSensorsEntry 4 }

zwaveUltravioletSensorLocation OBJECT-TYPE
    SYNTAX              DisplayString
    MAX-ACCESS          read-write
    STATUS              current
    DESCRIPTION
        "Z-wave ultraviolet sensor location"
    ::= { zwaveUltravioletSensorsEntry 5 }

zwaveUltravioletSensorValue OBJECT-TYPE
    SYNTAX              Numeric2
    MAX-ACCESS          read-write
    STATUS              current
    DESCRIPTION
        "Z-wave ultraviolet sensor value"
    ::= { zwaveUltravioletSensorsEntry 6 }

--- Luminance Sensors

zwaveLuminanceSensorsCount OBJECT-TYPE
    SYNTAX              Integer32
    MAX-ACCESS          read-write
    STATUS              current
    DESCRIPTION
        "Z-wave luminance sensors count"
    ::= { zwaveLuminanceSensors 1 }

zwaveLuminanceSensorsTable OBJECT-TYPE
    SYNTAX              SEQUENCE OF ZwaveLuminanceSensorsEntry
    MAX-ACCESS          not-accessible
    STATUS              current
    DESCRIPTION
        "Z-wave luminance sensors table"
    ::= { zwaveLuminanceSensors 2 }

zwaveLuminanceSensorsEntry OBJECT-TYPE
    SYNTAX              ZwaveLuminanceSensorsEntry
    MAX-ACCESS          not-accessible
    STATUS              current
    DESCRIPTION
	   "Z-wave luminance sensots entry"
    INDEX   { zwaveLuminanceSensorIndex }
    ::= { zwaveLuminanceSensorsTable 1 }

ZwaveLuminanceSensorsEntry ::= SEQUENCE {
    zwaveLuminanceSensorIndex     INTEGER(0..255),
    zwaveLuminanceSensorNodeId    Integer32,
    zwaveLuminanceSensorId        DisplayString,
    zwaveLuminanceSensorName      DisplayString,
    zwaveLuminanceSensorLocation  DisplayString,
    zwaveLuminanceSensorValue     Numeric2
}

zwaveLuminanceSensorIndex OBJECT-TYPE
    SYNTAX              INTEGER(0..255)
    MAX-ACCESS          not-accessible
    STATUS              current
    DESCRIPTION
        "Z-wave luminance sensor index"
    ::= { zwaveLuminanceSensorsEntry 1 }

zwaveLuminanceSensorNodeId OBJECT-TYPE
    SYNTAX              Integer32
    MAX-ACCESS          read-write
    STATUS              current
    DESCRIPTION
        "Z-wave luminance sensor node id"
    ::= { zwaveLuminanceSensorsEntry 2 }

zwaveLuminanceSensorId OBJECT-TYPE
    SYNTAX              DisplayString
    MAX-ACCESS          read-write
    STATUS              current
    DESCRIPTION
        "Z-wave luminance sensor id"
    ::= { zwaveLuminanceSensorsEntry 3 }

zwaveLuminanceSensorName OBJECT-TYPE
    SYNTAX              DisplayString
    MAX-ACCESS          read-write
    STATUS              current
    DESCRIPTION
        "Z-wave luminance sensor name"
    ::= { zwaveLuminanceSensorsEntry 4 }

zwaveLuminanceSensorLocation OBJECT-TYPE
    SYNTAX              DisplayString
    MAX-ACCESS          read-write
    STATUS              current
    DESCRIPTION
        "Z-wave luminance sensor location"
    ::= { zwaveLuminanceSensorsEntry 5 }

zwaveLuminanceSensorValue OBJECT-TYPE
    SYNTAX              Numeric2
    MAX-ACCESS          read-write
    STATUS              current
    DESCRIPTION
        "Z-wave luminance sensor value"
    ::= { zwaveLuminanceSensorsEntry 6 }

--- Humidity Sensors

zwaveHumiditySensorsCount OBJECT-TYPE
    SYNTAX              Integer32
    MAX-ACCESS          read-write
    STATUS              current
    DESCRIPTION
        "Z-wave humidity sensors count"
    ::= { zwaveHumiditySensors 1 }

zwaveHumiditySensorsTable OBJECT-TYPE
    SYNTAX              SEQUENCE OF ZwaveHumiditySensorsEntry
    MAX-ACCESS          not-accessible
    STATUS              current
    DESCRIPTION
        "Z-wave humidity sensors table"
    ::= { zwaveHumiditySensors 2 }

zwaveHumiditySensorsEntry OBJECT-TYPE
    SYNTAX              ZwaveHumiditySensorsEntry
    MAX-ACCESS          not-accessible
    STATUS              current
    DESCRIPTION
	   "Z-wave humidity sensots entry"
    INDEX   { zwaveHumiditySensorIndex }
    ::= { zwaveHumiditySensorsTable 1 }

ZwaveHumiditySensorsEntry ::= SEQUENCE {
    zwaveHumiditySensorIndex     INTEGER(0..255),
    zwaveHumiditySensorNodeId    Integer32,
    zwaveHumiditySensorId        DisplayString,
    zwaveHumiditySensorName      DisplayString,
    zwaveHumiditySensorLocation  DisplayString,
    zwaveHumiditySensorValue     Numeric2
}

zwaveHumiditySensorIndex OBJECT-TYPE
    SYNTAX              INTEGER(0..255)
    MAX-ACCESS          not-accessible
    STATUS              current
    DESCRIPTION
        "Z-wave humidity sensor index"
    ::= { zwaveHumiditySensorsEntry 1 }

zwaveHumiditySensorNodeId OBJECT-TYPE
    SYNTAX              Integer32
    MAX-ACCESS          read-write
    STATUS              current
    DESCRIPTION
        "Z-wave humidity sensor node id"
    ::= { zwaveHumiditySensorsEntry 2 }

zwaveHumiditySensorId OBJECT-TYPE
    SYNTAX              DisplayString
    MAX-ACCESS          read-write
    STATUS              current
    DESCRIPTION
        "Z-wave humidity sensor id"
    ::= { zwaveHumiditySensorsEntry 3 }

zwaveHumiditySensorName OBJECT-TYPE
    SYNTAX              DisplayString
    MAX-ACCESS          read-write
    STATUS              current
    DESCRIPTION
        "Z-wave humidity sensor name"
    ::= { zwaveHumiditySensorsEntry 4 }

zwaveHumiditySensorLocation OBJECT-TYPE
    SYNTAX              DisplayString
    MAX-ACCESS          read-write
    STATUS              current
    DESCRIPTION
        "Z-wave humidity sensor location"
    ::= { zwaveHumiditySensorsEntry 5 }

zwaveHumiditySensorValue OBJECT-TYPE
    SYNTAX              Numeric2
    MAX-ACCESS          read-write
    STATUS              current
    DESCRIPTION
        "Z-wave humidity sensor value"
    ::= { zwaveHumiditySensorsEntry 6 }

---
--- Object Groups, Conformance, Compilances
---

zeyeConformance         OBJECT IDENTIFIER ::= { zeye 1 }

zeyeCompliances         OBJECT IDENTIFIER ::= { zeyeConformance 1 }
zeyeGroups              OBJECT IDENTIFIER ::= { zeyeConformance 2 }

zeyeCommonCompliances MODULE-COMPLIANCE
    STATUS  current
    DESCRIPTION
            "The compliance statement for Zeye common entities."
    MODULE  -- this module
        MANDATORY-GROUPS { commonObjectGroup }
    ::= { zeyeCompliances 1 }

zeyeZwaveCompliances MODULE-COMPLIANCE
    STATUS  current
    DESCRIPTION
            "The compliance statement for Zeye zwave entities."
    MODULE  -- this module
        MANDATORY-GROUPS { zwaveObjectGroup }
    ::= { zeyeCompliances 2 }

commonObjectGroup OBJECT-GROUP
    OBJECTS {
        zeyeAgentVersion
    }
    STATUS current
    DESCRIPTION
        "ZEYE-MIB common objects group"
    ::= { zeyeGroups 1 }

zwaveObjectGroup OBJECT-GROUP
    OBJECTS {
        zwaveNodesCount,
        zwaveNodeId,
        zwaveNodeName,
        zwaveNodeLocation,
        zwaveNodeBaud,
        zwaveNodeBattery,
        zwaveNodeAwaked,
        zwaveNodeType,
        zwaveNodeTypeName,
        zwaveTemperatureSensorsCount,
        zwaveTemperatureSensorNodeId,
        zwaveTemperatureSensorId,
        zwaveTemperatureSensorName,
        zwaveTemperatureSensorLocation,
        zwaveTemperatureSensorValue
    }
    STATUS current
    DESCRIPTION
        "ZEYE-MIB z-wave objects group"
    ::= { zeyeGroups 2 }

END
